# fred_catalog
FRED Metadata Catalog (ADIT2200, Fall 2026). Generated by src/build_fred_requirements.m.

## CARD: Cardinality: every crow's-foot constraint on the ERD holds in the graph (Container)
Neo4j Community cannot declare cardinality. Each constraint is a query in neo4j/cypher/fred_degree_audit.cypher whose expected answer is zero rows. Rules A01 to A05 tolerate the data-list series (dataset_id set).

### A01: fk_series_release: every Series is in exactly one Release (Functional)
fk_series_release: every Series is in exactly one Release. Known exception: the 41 data-list series (dataset_id set) came from the FRED data-list archive, not the series API, and carry release as text only. They should be 0 here once the catalog crawl reaches them.

### A02: fk_series_frequency: exactly one Frequency (Functional)
fk_series_frequency: exactly one Frequency.

### A03: fk_series_units: exactly one Units (Functional)
fk_series_units: exactly one Units.

### A04: fk_series_sa: exactly one SeasonalAdjustment (Functional)
fk_series_sa: exactly one SeasonalAdjustment.

### A05: series_category (rule 5): a series is classified in at least one category (Functional)
series_category (rule 5): a series is classified in at least one category. Zero is the data-list exception again.

### A06: release_source (rule 1): every release is published by at least one source (Functional)
release_source (rule 1): every release is published by at least one source. Mandatory on the release side in the ERD.

### A07: fk_release_date_release (weak entity, rule 2): a ReleaseDate belongs to exactly one Release (Functional)
fk_release_date_release (weak entity, rule 2): a ReleaseDate belongs to exactly one Release. The FK direction is reversed in the graph (Release-[:SCHEDULED_ON]->ReleaseDate), so count incoming edges.

### A08: fk_category_parent (unary 1:M): at most one parent, and zero only for the root (is_root = true) (Functional)
fk_category_parent (unary 1:M): at most one parent, and zero only for the root (is_root = true).

### A09: fk_tag_tag_group (rule 8): exactly one TagGroup (Functional)
fk_tag_tag_group (rule 8): exactly one TagGroup.

### A10: Document layer (graph only): a Document describes exactly one Release, and a Chunk belongs to exactly one Document (Functional)
Document layer (graph only): a Document describes exactly one Release, and a Chunk belongs to exactly one Document.

### A11: Chunk<-HAS_CHUNK (Functional)
See the statement labelled A11 in the audit file.

### A12: Lineage (graph only): a SeriesVariant belongs to exactly one Series and is available in exactly one SourceMember (Functional)
Lineage (graph only): a SeriesVariant belongs to exactly one Series and is available in exactly one SourceMember.

### A13: Dangling business keys: the FK value kept as a property must agree with the edge (the graph stores both; they can drift) (Functional)
Dangling business keys: the FK value kept as a property must agree with the edge (the graph stores both; they can drift).

### A14: Chunk.doc_id drift (Functional)
See the statement labelled A14 in the audit file.

### A15: fk_rte_release (rule 12): a ReleaseTableElement is listed in exactly one Release (Functional)
fk_rte_release (rule 12): a ReleaseTableElement is listed in exactly one Release.

### A16: fk_rte_parent (unary 1:M, rule 12): an element has one parent, except a top-level section (parent_key absent), which has none (Functional)
fk_rte_parent (unary 1:M, rule 12): an element has one parent, except a top-level section (parent_key absent), which has none.

### A17: SHOWS (graph only, no FK in SQL): a series row shows at most one Series, and only a series row shows one (Functional)
SHOWS (graph only, no FK in SQL): a series row shows at most one Series, and only a series row shows one. Zero on a series row is allowed: the catalog holds a subset of each release's series.

## MODEL: One checked model: diagrams, DDL and live stores never disagree (Container)
src/+dbdesign/fred_relational_model.m is the single source; every other representation is compared with it.

### M01: The model matches sql/fred_schema.sql (PostgreSQL) (Functional)
Tables, column order, declared types, NOT NULL, defaults, keys, foreign keys with ON DELETE, CHECK constraints and indexes.

### M02: The model matches sql/mysql/fred_schema.sql (MySQL/MariaDB) (Functional)
Same comparison for the MySQL dialect.

### M03: The graph model covers the relational model (Functional)
Every table is a label, a join table turned relationship, or listed as excluded; every foreign key is a relationship or excluded.

### M04: The live PostgreSQL catalog matches the model (Functional)
information_schema and pg_catalog agree with the model, including triggers, functions and procedures.

### M05: The live Neo4j database matches the graph model (Functional)
Labels, property types, relationship patterns, uniqueness constraints and indexes agree with dbdesign.fred_graph_model.

### M06: Every diagram names every table, label and relationship it documents (Functional)
The logical, FD-map, table-map, physical and graph views are rendered from the model and compile with Graphviz.

### M07: The degree audit names only relationship types the graph model declares (Functional)
Seventeen statements A01..A17 in order, each returning a rule column.

## READ: MATLAB reads the catalog with the same as-of semantics as SQL (Container)
src/fred_series.m, fred_panel.m, fred_series_sql.m and fred_pg_query.m: the regression-side entry point to PostgreSQL.

### R01: A vintage read in MATLAB equals value_as_of in SQL (Functional)
For any series, period and vintage date, fred_series(id, Vintage=d) returns the value value_as_of(id, period, d) returns, and every row's real-time window contains d.

### R02: Today's read is the set of open real-time windows (Functional)
fred_series(id) and Vintage="latest" return one row per period, the rows with realtime_end = 9999-12-31, in date order.

### R03: The first-published read covers every period exactly once (Functional)
Vintage="first" returns one row per observation_date with the smallest realtime_start.

### R04: Series metadata on the timetable comes from the series row (Functional)
Title, units, frequency, seasonal adjustment and release are read from the catalog, not typed by the caller.

### R05: A panel is the outer join of its series on observation date (Functional)
One column per id, union of dates, NaN where a series has no period; frequencies are not reconciled.

### R06: Only identifiers reach the SQL statement (Functional)
A series id is letters, digits, underscore, dot or hyphen; anything else is refused before any query is built.

## GDSS: Forecast adapters honour the fit-payload contract (Container)

### G01: The naive random-walk fit payload carries all six uncertainty fields (Functional)
parameter_covariance, parameter_standard_error, each with _status and _reference. Regression for commit ab38d13, which spliced two assignments into one line.
